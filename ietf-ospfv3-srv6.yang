module ietf-ospfv3-srv6 {
  yang-version 1.1;
  namespace "urn:ietf:params:xml:ns:"
          + "yang:ietf-ospfv3-srv6";
  prefix ospfv3-srv6;

  import ietf-yang-types {
    prefix yang;
    reference
      "RFC 6991: Common YANG Data Types";
  }
  import ietf-routing-types {
    prefix rt-types;
    reference
      "RFC 8294: Common YANG Data Types for the Routing Area";
  }
  import ietf-routing {
    prefix rt;
    reference
      "RFC 8349: A YANG Data Model for Routing
                 Management (NMDA Version)";
  }
  import ietf-ospfv3-extended-lsa {
    prefix ospfv3-e-lsa;
    reference
      "RFC 9587: YANG Data Model for OSPFv3 Extended Link State
                 Advertisements (LSAs)";
  }
  import ietf-ospf {
    prefix ospf;
    reference
      "RFC 9129: YANG Data Model for the OSPF Protocol";
  }
  import ietf-srv6-base {
    prefix srv6;
  }
  import ietf-inet-types {
    prefix inet;
    reference
      "RFC 6991: Common YANG Data Types";
  }
  import ietf-segment-routing {
    prefix sr;
    reference
      "RFC 9020: YANG Data Model for Segment Routing";
  }

  organization
    "IETF LSR Working Group";
  contact
    "WG Web:   <https://datatracker.ietf.org/group/lsr/>
     WG List:  <mailto:lsr@ietf.org>

     Author:    Yingzhen Qu
                <mailto:yingzhen.ietf@gmail.com>
     Author:    Zhibo Hu
                <mailto:huzhibo@huawei.com>
     Author:    Xuesong Geng
                <mailto:gengxuesong@huawei.com>
     Author:    Kamran Raza
                <mailto:skraza@cisco.com>
     Author:    Acee Lindem
                <mailto:acee.ietf@gmail.com>
    ";
  description
    "The YANG module defines the configuration and operational state
     for OSPFv3 extensions to support Segment Routing over IPv6 data
     plane as defined in RFC9513.

     This YANG model conforms to the Network Management
     Datastore Architecture (NDMA) as described in RFC 8342.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2025-02-28 {
    description
      "Initial revision.";
    reference
      "RFC XXXX: YANG Data Model for OSPF SRv6";
  }

  /* Identities */

  identity SRV6_END_FUNC_TYPE {
    description
      "Base identity type for srv6 endpoint function code points.";
  }

  identity SRV6_END_FUNC_NO_PSP_USP {
    base SRV6_END_FUNC_TYPE;
    description
      "End (no PSP, no USP).";
  }

  identity SRV6_END_FUNC_PSP {
    base SRV6_END_FUNC_TYPE;
    description
      "End with PSP.";
  }

  identity SRV6_END_FUNC_USP {
    base SRV6_END_FUNC_TYPE;
    description
      "END with USP.";
  }

  identity SRV6_END_FUNC_PSP_USP {
    base SRV6_END_FUNC_TYPE;
    description
      "END with PSP & USP.";
  }

  identity SRV6_END_T_FUNC_NO_PSP_USP {
    base SRV6_END_FUNC_TYPE;
    description
      "End.T (no PSP, no USP).";
  }

  identity SRV6_END_T_FUNC_PSP {
    base SRV6_END_FUNC_TYPE;
    description
      "End.T with PSP.";
  }

  identity SRV6_END_T_FUNC_USP {
    base SRV6_END_FUNC_TYPE;
    description
      "End.T with USP.";
  }

  identity SRV6_END_T_FUNC_PSP_USP {
    base SRV6_END_FUNC_TYPE;
    description
      "End.T with PSP & USP.";
  }

  identity SRV6_END_X_FUNC_NO_PSP_USP {
    base SRV6_END_FUNC_TYPE;
    description
      "End.x (no PSP, no USP).";
  }

  identity SRV6_END_X_FUNC_PSP {
    base SRV6_END_FUNC_TYPE;
    description
      "End.x with PSP.";
  }

  identity SRV6_END_X_FUNC_USP {
    base SRV6_END_FUNC_TYPE;
    description
      "End.x with USP.";
  }

  identity SRV6_END_X_FUNC_PSP_USP {
    base SRV6_END_FUNC_TYPE;
    description
      "End.x with PSP & USP.";
  }

  identity SRV6_END_FUNC_DX6 {
    base SRV6_END_FUNC_TYPE;
    description
      "End.DX6 function.";
  }

  identity SRV6_END_FUNC_DT6 {
    base SRV6_END_FUNC_TYPE;
    description
      "End.DT6 function.";
  }

  identity SRV6_END_FUNC_OTP {
    base SRV6_END_FUNC_TYPE;
    description
      "END.OTP.";
  }

  identity s1-bit {
    base ospf:ospfv3-lsa-option;
    description
      "The S1/S2 bits are dependent on the desired
       flooding scope for the LSA.";
  }

  identity s2-bit {
    base ospf:ospfv3-lsa-option;
    description
      "The S1/S2 bits are dependent on the desired
       flooding scope for the LSA.";
  }

  identity srv6-locator-lsa {
    base ospf:ospfv3-lsa-type;
    description
      "SRv6 Locator LSA - Type TBD";
  }

  identity LOCATOR-ROUTE-TYPE {
    description
      "The type of the locator route.";
  }

  identity INTRA-AREA-LOCATOR {
    base LOCATOR-ROUTE-TYPE;
    description
      "Intra-Area";
  }

  identity INTER-AREA-LOCATOR {
    base LOCATOR-ROUTE-TYPE;
    description
      "Inter-Area";
  }

  identity AS-EXTERNAL-LOCATOR {
    base LOCATOR-ROUTE-TYPE;
    description
      "AS External";
  }

  identity NSSA-EXTERNAL-LOCATOR {
    base LOCATOR-ROUTE-TYPE;
    description
      "NSSA External";
  }

  identity srv6-capability-bit {
    description
      "Base identity for SRv6 capability TLV bits.";
  }

  identity o-bit {
    base srv6-capability-bit;
    description
      "O-flag.";
    reference
      "RFC 9259: Operations, Administration, and Maintenance (OAM)
       in Segment Routing over IPv6 (SRv6)";
  }

  identity srv6-end-sid-bit {
    description
      "Base identity for SRv6 End SID sub-TLV bits.";
  }

  identity srv6-endx-sid-bit {
    description
      "Base identity for SRv6 End.X SID sub-TLV bits.";
  }

  identity b-bit {
    base srv6-endx-sid-bit;
    description
      "B-flag. Backup flag. If set, the End.X sid is
       eligible for protection.";
  }

  identity s-bit {
    base srv6-endx-sid-bit;
    description
      "S-flag. Set flag. When set, the End.X sid refers to
       a set of adjacencies (and therefore May be assigned
       to other adjacencies as well.";
  }

  identity p-bit {
    base srv6-endx-sid-bit;
    description
      "P-flag. Persistent flag. When set, the End.X sid is
       persistently allocated, i.e., the End.x sid value
       remains consistent across router restart and/or
       interface flap.";
  }

  identity ac-bit {
    base ospfv3-e-lsa:ospfv3-e-prefix-option;
    description
      "When the prefix/SRv6 Locator is configured as anycast,
       the AC-bit MUST be set. Otherwise, this flag MUST be
       clear.";
    reference
      "draft-ietf-lsr-ospfv3-srv6-extensions";
  }

  /* typedef */

  typedef srv6-sid-value {
    type inet:ipv6-address-no-zone;
    description
      "16 Octets encoded sid value.";
  }

  /* Features */

  feature srv6-ti-lfa {
    description
      "Enhance SRv6 FRR with ti-lfa
       support";
  }

  /* Groupings */

  grouping srv6-capabilities {
    description
      "SRV6 capability grouping.";
    container srv6-capability {
      description
        "SRv6 capability.";
      leaf-list flags {
        type identityref {
          base srv6-capability-bit;
        }
        description
          "SRv6 Capability TLV flag bits list.";
      }
    }
  }

  grouping srv6-endpoint-func {
    description
      "This group defines srv6 endpoint function";
    container endpoint-func {
      description
        "SRv6 Endpoint function Descriptor.";
      leaf-list flags {
        type identityref {
          base srv6-end-sid-bit;
        }
        description
          "SRv6 End SID sub-TLV  flag bits list. No flags
           are currently being defined.";
      }
      leaf endpoint-func {
        type identityref {
          base SRV6_END_FUNC_TYPE;
        }
        description
          "The endpoint function.";
      }
      leaf undefined-endpoint-func {
        type uint16;
        description
          "Unknown endpoint func value.";
      }
    }
  }

  grouping srv6-end-sids {
    description
      "This group defines srv6 end sid";
    container srv6-end-sid {
      description
        "SRv6 Segment Identifier(SID) with Endpoint functions.";
      leaf-list flags {
        type identityref {
          base srv6-end-sid-bit;
        }
        description
          "SRv6 end sid flags.";
      }
      uses srv6-endpoint-func;
      leaf sid {
        type srv6-sid-value;
        description
          "SRV6 sid value.";
      }
      uses srv6-sid-structures;
    }
  }

  grouping srv6-sid-structures {
    description
      "This group defines SRv6 SID Structure sub-TLV.";
    container srv6-sid-structure {
      description
        "SRv6 SID Structure sub-TLV is used to advertise the length
         of each individual part of the SRv6 SID as defined in
         [I-D.ietf-spring-srv6-network-programming]";
      leaf lb-length {
        type uint8;
        description
          "SRv6 SID Locator Block length in bits.";
      }
      leaf ln-length {
        type uint8;
        description
          "SRv6 SID Locator Node length in bits.";
      }
      leaf fun-length {
        type uint8;
        description
          "SRv6 SID Function length in bits.";
      }
      leaf arg-length {
        type uint8;
        description
          "SRv6 SID Argument length in bits.";
      }
    }
  }

  grouping srv6-endx-sids {
    description
      "This group defines SRv6 SIDs Associated with Adjacencies
       including SRv6 End.X SID Sub-TLV and SRv6 LAN End.X SID
       Sub-TLV.";
    container srv6-endx-sid {
      description
        "SRv6 sids associated with an adjacency.";
      uses srv6-endpoint-func;
      leaf-list func-flags {
        type identityref {
          base srv6-endx-sid-bit;
        }
        description
          "Flags for SRv6 end x SID.";
      }
      leaf algorithm {
        type uint8;
        description
          "Associated algorithm.";
      }
      leaf weight {
        type uint8;
        description
          "8 bit field whose value represents the weight of the End.X
           SID for the purpose of load balancing";
      }
      leaf-list sid {
        type srv6-sid-value;
        description
          "SRV6 sid value.";
      }
      leaf neighbor-router-id {
        type yang:dotted-quad;
        description
          "Neighbor router ID.This is only
           used on LAN adjacencies.";
      }
      uses srv6-sid-structures;
    }
  }

  grouping srv6-locator-lsas {
    description
      "Grouping for SRv6 locator lsas.";
    container srv6-localtor-lsas {
      description
        "SRv6 locator lsas.";
      list srv6-locator-lsa {
        description
          "List of SRv6 locator lsa.";
        leaf link-state-id {
          type uint32;
          description
            "Link State ID.";
        }
        leaf adv-router {
          type rt-types:router-id;
          description
            "Advertising router id.";
        }
        list sr6-locator-tlv {
          description
            "List of tlvs in SRv6 locator lsa.";
          container srv6-locactor-tlvs {
            description
              "This contains a SRv6 locator tlv.";
            leaf route-type {
              type identityref {
                base LOCATOR-ROUTE-TYPE;
              }
              description
                "The type of the locator route";
            }
            leaf algorithm {
              type uint8;
              description
                "Associated algorithm.";
            }
            leaf locator-length {
              type uint8;
              description
                "Carries the length of the Locator
                 prefix as number of bits (1-128)";
            }
            leaf-list flags {
              type identityref {
                base ospfv3-e-lsa:ospfv3-e-prefix-option;
              }
              description
                "Flags for srv6 locator tlv.";
            }
            leaf metric {
              type uint32;
              description
                "Metric value.";
            }
            leaf-list locator {
              type inet:ipv6-address-no-zone;
              description
                "Advertised SRV6 locator.";
            }
            uses srv6-end-sids;
          }
          container unknown-tlv {
            uses ospf:tlv;
            description
              "Unknow tlv.";
          }
        }
      }
    }
  }

  /* Cfg */

  augment "/rt:routing/"
        + "rt:control-plane-protocols/rt:control-plane-protocol"
        + "/ospf:ospf" {
    when "../rt:type = 'ospf:ospfv3'" {
      description
        "This augment OSPFv3 routing protocol when used";
    }
    description
      "This augments OSPFv3 protocol configuration
       with SRv6.";
    container srv6 {
      leaf enable {
        type boolean;
        default "false";
        description
          "Enables SRv6 protocol extensions.";
      }
      leaf default-locator {
        type boolean;
        default "false";
        description
          "Enable OSPFv3 segment-routing IPv6 with default Locator.";
      }
      leaf-list locator-name {
        when "not(../default-locator='true')" {
          description
            "Only applies to non default locator.";
        }
        type leafref {
          path "/rt:routing/sr:segment-routing/srv6:srv6"
             + "/srv6:locators/srv6:locator/srv6:name";
        }
        description
          "Enable OSPFv3 segment-routing IPv6 with specified
           locator.";
      }
      leaf persistent-end-x-sid {
        type boolean;
        default "false";
        description
          "Enable the persistent nature of End.X sid";
      }
      description
        "Configuration about OSPFv3 segment-routing IPv6.";
    }
    container micro-loop-avoidance {
      leaf srv6-enable {
        type boolean;
        default "false";
        description
          "Enable SRv6 avoid-microloop.Depend on SR IPv6 Enable.";
      }
      leaf srv6-rib-update-delay {
        type uint16 {
          range "1000..10000";
        }
        units "ms";
        default "5000";
        description
          "Set the route delivery delay for SRv6 avoid-microloop.
           Depend on SR IPv6 Enable.";
      }
      description
        "Enable OSPFv3 avoid-microloop.";
    }
  }

  augment "/rt:routing/"
        + "rt:control-plane-protocols/rt:control-plane-protocol"
        + "/ospf:ospf/ospf:fast-reroute" {
    when "../../rt:type = 'ospf:ospfv3'" {
      description
        "This augment OSPFv3 routing protocol when used";
    }
    description
      "This augments OSPFv3 IP FRR with IPV6 TILFA.";
    container srv6-ti-lfa {
      if-feature "srv6-ti-lfa";
      leaf enable {
        type boolean;
        description
          "Enables SRv6 TI-LFA computation.";
      }
      description
        "SRv6 TILFA configuration.";
    }
  }

  /* Database */
  augment "/rt:routing/"
        + "rt:control-plane-protocols/rt:control-plane-protocol/"
        + "ospf:ospf/ospf:areas/ospf:area/"
        + "ospf:interfaces/ospf:interface/ospf:database/"
        + "ospf:link-scope-lsa-type/ospf:link-scope-lsas/"
        + "ospf:link-scope-lsa/ospf:version/ospf:ospfv3/"
        + "ospf:ospfv3/ospf:body" {
    when "../../../../../../../../../../../rt:type = 'ospf:ospfv3'" {
      description
        "This augment OSPFv3 routing protocol when used";
    }
    description
      "This augments OSPFv3 database with link scope SRv6 locator
       lsas.";

    uses srv6-locator-lsas;
  }

  augment "/rt:routing/"
        + "rt:control-plane-protocols/rt:control-plane-protocol/"
           + "ospf:ospf/ospf:areas/ospf:area/ospf:database/"
           + "ospf:area-scope-lsa-type/ospf:area-scope-lsas/"
           + "ospf:area-scope-lsa/ospf:version/ospf:ospfv3/"
           + "ospf:ospfv3/ospf:body" {
    when "../../../../../../../../../rt:type = 'ospf:ospfv3'" {
      description
        "This augment OSPFv3 routing protocol when used";
    }
    description
      "This augments OSPFv3 database with area scope SRv6 locator
       lsas.";

    uses srv6-locator-lsas;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body" {
    when "../../../../../../../rt:type = 'ospf:ospfv3'" {
      description
        "This augment OSPFv3 routing protocol when used";
    }
    description
      "This augments OSPFv3 database with as scope SRv6 locator
       lsas.";

    uses srv6-locator-lsas;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv3/"
        + "ospf:ospfv3/ospf:body/ospf:router-information" {
    when "../../../../../../../../../../"
       + "rt:type = 'ospf:ospfv3'" {
      description
        "This augmentation is only valid for OSPFv3.";
    }
    description
      "Area scope OSPFv3 Router Information LSA.";
    uses srv6-capabilities;
    uses srv6:srv6-msd-signaled;    
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospf:router-information" {
    when "../../../../../../../../rt:type = 'ospf:ospfv3'" {
      description
        "This augment OSPFv3 routing protocol when used";
    }
    description
      "This augments OSPFv3 protocol router capability.";
    uses srv6-capabilities;
    uses srv6:srv6-msd-signaled;
  }

  augment "/rt:routing/rt:control-plane-protocols"
        + "/rt:control-plane-protocol/ospf:ospf/ospf:areas/ospf:area"
        + "/ospf:database/ospf:area-scope-lsa-type"
        + "/ospf:area-scope-lsas"
        + "/ospf:area-scope-lsa/ospf:version/ospf:ospfv3"
        + "/ospf:ospfv3/ospf:body/ospfv3-e-lsa:e-router/"
        + "ospfv3-e-lsa:e-router-tlvs/"
        + "ospfv3-e-lsa:link-tlv" {
    when "../../../../../../../../../../../../rt:type"
       + "= 'ospf:ospfv3'" {
      description
        "This augment OSPFv3 routing protocol when used";
    }
    description
      "This augments OSPFv3 protocol neighbor.";
    uses srv6-endx-sids;
    uses srv6:srv6-msd-signaled;
  }

  /* Notifications */
}
